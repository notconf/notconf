module test {
  yang-version 1.1;
  namespace "urn:notconf:test";
  prefix test;

  feature alice-feature {
    description
      "This feature enables alice container";
  }

  container bob {
    leaf startup {
      type string;
    }
    leaf bert {
      type string;
    }
    container state {
      config false;
      leaf great {
        type string;
      }
    }

    container alice {
      if-feature alice-feature;
      leaf startup {
        type string;
      }
    }
  }
}
